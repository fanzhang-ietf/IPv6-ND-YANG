module ietf-ipv6-nd {
  yang-version 1.1;
  namespace "urn:ietf:params:xml:ns:yang:ietf-ipv6-nd";
  prefix v6nd;

  import ietf-yang-types {
    prefix yang;
    reference
      "RFC 9911: Common YANG Data Types";
  }
  import ietf-interfaces {
    prefix if;
    reference
      "RFC 8343: A Yang Data Model for Interface Management";
  }
  import ietf-ip {
    prefix ip;
    reference
      "RFC 8344: A Yang Data Model for IP Management";
  }

  organization
    "IETF 6MAN (IPv6 Maintenance) Working Group";

  contact
    "WG Web:  <https://datatracker.ietf.org/wg/6man/>
     WG List: 6MAN <mailto:ipv6@ietf.org>

     Author:  Fan Zhang
              <zhangf52@chinatelecom.cn>
     Author:  Yongqing Zhu
              <zhuyq8@chinatelecom.cn>
     Author:  Bo Wu
              <lana.wubo@huawei.com>
     Author:  Jiayuan Hu
              <hujy5@chinatelecom.cn>";

  description
    "This YANG module defines a YANG data model to configure and 
     manage IPv6 Neighbor Discovery (ND) and related functions, 
     including IPv6 address resolution, redirect, proxy Neighbor
     Advertisement, Neighbor Unreachability Detection (NUD), 
     Duplicate Address Detection (DAD), and Enhanced DAD.

     Copyright (c) 2026 IETF Trust and the persons
     identified as authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see
     the RFC itself for full legal notices.";

  // RFC Ed: replace '2026-04-20' with the module publication date
  // the format is (YYYY-MM-DD)

  // replace XXXX with actual RFC number and remove
  // this note

  revision 2026-04-20 {
    description
      "Initial version.";
    reference
      "RFC XXXX: YANG Data Model for IPv6 Neighbor Discovery";
  }

  
  /* Groupings */
  
  grouping nd-basic-statistics {
    description
      "Grouping for basic statistics for IPv6 ND messages.";
    leaf in-pkts {
      type yang:counter64;
      description
        "The total number of packets received.";
    }
    leaf out-pkts {
      type yang:counter64;
      description
        "The total number of packets transmitted.";
    }
    leaf drop-pkts {
      type yang:counter64;
      description
        "The total number of packets discarded.";
    }    
  }

  grouping nd-unicast-multicast-statistics {
    description
      "Grouping for statistics for IPv6 ND messages categorized by 
       unicast and multicast.";
    leaf in-unicast-pkts {
      type yang:counter64;
      description
        "The total number of packets received with the destination 
         address as a unicast address.";
    }
    leaf in-multicast-pkts {
      type yang:counter64;
      description
        "The total number of packets received with the destination 
         address as a multicast address.";
    }
    leaf out-unicast-pkts {
      type yang:counter64;
      description
        "The total number of packets transmitted with the destination 
         address as a unicast address.";
    }
    leaf out-multicast-pkts {
      type yang:counter64;
      description
        "The total number of packets transmitted with the destination 
         address as a multicast address.";
    }
  }

  grouping nd-drop-statistics {
    description
      "Grouping for statistics for IPv6 ND messages discarded by 
       reason.";
    leaf drop-bad-code-pkts {
      type yang:counter64;
      description
        "The total number of packets discarded due to invalid code.";
    }
    leaf drop-bad-hoplimit-pkts {
      type yang:counter64;
      description
        "The total number of packets discarded due to invalid hop 
         limits.";
    }
    leaf drop-bad-len-pkts {
      type yang:counter64;
      description
        "The total number of packets discarded due to invalid length.";
    }
    leaf drop-bad-option-pkts {
      type yang:counter64;
      description
        "The total number of packets discarded due to invalid option.";
    }    
    leaf drop-checksum-err-pkts {
      type yang:counter64;
      description
        "The total number of packets discarded due to checksum errors.";
    }    
    leaf drop-fragmented-pkts {
      type yang:counter64;
      description
        "The total number of packets discarded due to fragmentation.";
    }
  }  

  /* Data nodes */

  augment "/if:interfaces/if:interface/ip:ipv6" {
    description
      "Augments interface configuration and state data with
       parameters of IPv6 ND.";
    container nd {
      description
        "Parameters of IPv6 ND.";
      leaf reachable-time {
        type uint32 {
          range "1..3600000";
        }
        units "milliseconds";
        default "30000";
        description
          "The time to confirm a neighbor's reachability for NUD.";
        reference
          "RFC4861: Neighbor Discovery for IP version 6 (IPv6)
                    Section 6.3.2 - BaseReachableTime";
      }
      leaf retrans-timer {
        type uint32 {
          range "1..max";
        }
        units "milliseconds";
        default "1000";
        description
          "The interval of retransmitting Neighbor Solicitations to a
           neighbor for address resolution, NUD, or DAD.";
        reference
          "RFC4861: Neighbor Discovery for IP version 6 (IPv6)
                    Section 6.3.2 - RetransTimer";
      }
      leaf redirect {
        type boolean;
        default "false";
        description
          "Controls whether sending of ICMP Redirect messages
           on the interface is enabled or disabled.
            true -  Sending of ICMP Redirect messages is enabled,
            false - Sending of ICMP Redirect messages is disabled.";
        reference
          "RFC4861: Neighbor Discovery for IP version 6 (IPv6)
                    Section 8";
      }
      leaf proxy-na {
        type boolean;
        default "false";
        description
          "Controls whether proxies for one or more other nodes by
           sending proxy Neighbor Advertisement.
            true -  Proxy NA is enabled,
            false - Proxy NA is disabled.";
        reference
          "RFC4861: Neighbor Discovery for IP version 6 (IPv6)
                    Section 7.2.8";
      }
      container enhanced-dad {
        description
          "Parameters of Enhanced DAD algorithm.";
        leaf enable {
          type boolean;
          default "false";
          description
            "Controls whether Enhanced DAD algorithm is enabled or
             disabled.";
          reference
            "RFC7527: Enhanced Duplicate Address Detection
                      Section 4";
        }
        leaf auto-resolve {
          when "../enable = 'true'";
          type boolean;
          default "false";
          description
            "Controls whether the automated action is taken when
             detecting duplicates. A trusted router can log a system
             management message, drop the received ND message, and
             block the untrusted IPv6 host nodes from which the
             duplicate NS(DAD) or NA message was received.";
          reference
            "RFC7527: Enhanced Duplicate Address Detection
                      Section 5";
        }
        reference
          "RFC7527: Enhanced Duplicate Address Detection";
      }
      container statistics {
        config false;
        description
          "A collection of interface-related statistics about IPv6
           ND messages.";
        container ns-stats {
          description
            "Statistics for Neighbor Solicitation packets.";
          uses nd-basic-statistics;
          uses nd-unicast-multicast-statistics;
          uses nd-drop-statistics;
          leaf out-nud-pkts {
            type yang:counter64;
            description
              "The total number of NS packets transmitted for NUD.";
          }          
        }
        container na-stats {
          description
            "Statistics for Neighbor Advertisement packets.";
          uses nd-basic-statistics;
          uses nd-unicast-multicast-statistics;
          uses nd-drop-statistics;
          leaf in-solicited-pkts {
            type yang:counter64;
            description
              "The total number of solicited NA packets received.";
          }
          leaf in-unsolicited-pkts {
            type yang:counter64;
            description
              "The total number of unsolicited NA packets received.";
          }
          leaf in-override-pkts {
            type yang:counter64;
            description
              "The total number of override NA packets received.";
          }
          leaf in-nonoverride-pkts {
            type yang:counter64;
            description
              "The total number of non-override NA packets received.";
          }
          leaf out-solicited-pkts {
            type yang:counter64;
            description
              "The total number of solicited NA packets transmitted.";
          }
          leaf out-unsolicited-pkts {
            type yang:counter64;
            description
              "The total number of unsolicited NA packets transmitted.";
          }
          leaf out-override-pkts {
            type yang:counter64;
            description
              "The total number of override NA packets transmitted.";
          }
          leaf out-nonoverride-pkts {
            type yang:counter64;
            description
              "The total number of non-override NA packets 
               transmitted.";
          }       
        }
        container rs-stats {
          description
            "Statistics for Router Solicitation packets.";
          uses nd-basic-statistics;
          uses nd-unicast-multicast-statistics;
          uses nd-drop-statistics;
        }  
        container ra-stats {
          description
            "Statistics for Router Advertisement packets.";
          uses nd-basic-statistics;
          uses nd-unicast-multicast-statistics;
          uses nd-drop-statistics;
        }  
        container redirect-stats {
          description
            "Statistics for Redirect packets.";
          uses nd-basic-statistics;
          uses nd-drop-statistics;
        }
      }
    }
  }

  augment "/if:interfaces/if:interface/ip:ipv6/ip:neighbor" {
    description
      "Augments IPv6 neighbor list with parameters of IPv6 address
       resolution based on IPv6 ND.";
    leaf age {
      when "../ip:origin = 'dynamic'";
      type uint32;
      units "seconds";
      config false;
      description
        "The time that has passed since receipt of the last
         reachability confirmation for the neighbor. Ignored when the
         neighbor entry is static.";
      reference
        "RFC4861: Neighbor Discovery for IP version 6 (IPv6)
                  Section 7.3.3";
    }
  }
}
